# Model_Template

## AirportProcess (FMC:Actor)
- dcterms:type: uml:Activity
- SpecIF:Visibility: Private

## AirportProcess (SpecIF:Diagram)
- dcterms:type: uml:Diagram
- SpecIF:Visibility: Public

## Model_AirportProcess (SpecIF:Collection)
- dcterms:description: Author:s-sruesch.
  Created:01.10.2012 15:10.
  Title:.
  Comment:.
- dcterms:type: uml:Model
- SpecIF:Visibility: Private

## provide flight information (FMC:Actor)
- dcterms:type: uml:CallBehaviorAction
- SpecIF:Visibility: Public

## hand over baggage (FMC:Actor)
- dcterms:type: uml:CallBehaviorAction
- SpecIF:Visibility: Public

## Fork (FMC:Actor)
- dcterms:type: uml:ForkNode
- SpecIF:Visibility: Public

## registration of Passenger (FMC:Actor)
- dcterms:type: uml:CallBehaviorAction
- SpecIF:Visibility: Public

## check in baggage (FMC:Actor)
- dcterms:type: uml:CallBehaviorAction
- SpecIF:Visibility: Public

## security check (FMC:Actor)
- dcterms:type: uml:CallBehaviorAction
- SpecIF:Visibility: Public

## baggage security check (FMC:Actor)
- dcterms:type: uml:CallBehaviorAction
- SpecIF:Visibility: Public

## border control (FMC:Actor)
- dcterms:type: uml:CallBehaviorAction
- SpecIF:Visibility: Public

## uml:MergeNode R-8da17d7f-141e-4b98-9a26-b949e61b0bc7 (FMC:Actor)
- dcterms:title: NoName
- dcterms:type: uml:MergeNode
- SpecIF:Visibility: Public

## Board Passenger (FMC:Actor)
- dcterms:type: uml:CallBehaviorAction
- SpecIF:Visibility: Public

## Join2 (FMC:Actor)
- dcterms:type: uml:JoinNode
- SpecIF:Visibility: Public

## Airline perform flight (FMC:Actor)
- dcterms:type: uml:CallBehaviorAction
- SpecIF:Visibility: Public

## Baggage Handling System (FMC:Actor)
- dcterms:type: uml:CallBehaviorAction
- SpecIF:Visibility: Public

## Ground Handling Service build up bulk baggage cart (FMC:Actor)
- dcterms:type: uml:CallBehaviorAction
- SpecIF:Visibility: Public

## build up Unit Load Devices (FMC:Actor)
- dcterms:type: uml:CallBehaviorAction
- SpecIF:Visibility: Public

## Merge (FMC:Actor)
- dcterms:type: uml:MergeNode
- SpecIF:Visibility: Public

## Transport Unit Load Devices to parking position (FMC:Actor)
- dcterms:type: uml:CallBehaviorAction
- SpecIF:Visibility: Public

## Ground Handling Service Load Baggage (FMC:Actor)
- dcterms:type: uml:CallBehaviorAction
- SpecIF:Visibility: Public

## CabinProcess (FMC:Actor)
- dcterms:type: uml:CallBehaviorAction
- SpecIF:Visibility: Public

## Ready for Boarding (FMC:Actor)
- dcterms:type: uml:AcceptEventAction
- SpecIF:Visibility: Public

## Join1 (FMC:Actor)
- dcterms:type: uml:JoinNode
- SpecIF:Visibility: Public

## uml:ActivityPartition R-7794d557-a31b-4441-a576-f13b1f42c732 (FMC:Actor)
- dcterms:title: NoName
- dcterms:type: uml:ActivityPartition
- SpecIF:Visibility: Public

## Passenger Handling (FMC:Actor)
- dcterms:type: uml:ActivityPartition
- SpecIF:Visibility: Public

## Bagage Handling (FMC:Actor)
- dcterms:type: uml:ActivityPartition
- SpecIF:Visibility: Public

## uml:ActivityFinalNode R-cff8cccc-c718-4566-987c-da9cc4afad7c (FMC:Event)
- dcterms:title: NoName
- dcterms:type: uml:ActivityFinalNode
- SpecIF:Visibility: Public

## uml:InitialNode R-93b07a3b-9716-418f-a49a-de4eaaec3587 (FMC:Event)
- dcterms:title: NoName
- dcterms:type: uml:InitialNode
- SpecIF:Visibility: Public

## ReadytoBoard_Signal (FMC:Event)
- dcterms:type: uml:Signal
- SpecIF:Visibility: Private

## uml:ObjectFlow R-85178790-88ab-4da8-b3d7-e836021892c5 (FMC:State)
- dcterms:title: NoName
- dcterms:type: uml:ObjectFlow
- SpecIF:Visibility: Public

## uml:ObjectFlow R-66d6ec78-4152-434a-984d-ed5abe8756a1 (FMC:State)
- dcterms:title: NoName
- dcterms:type: uml:ObjectFlow
- SpecIF:Visibility: Public

## uml:ObjectFlow R-1f22f535-4c9d-4cee-b743-573de1111ccc (FMC:State)
- dcterms:title: NoName
- dcterms:type: uml:ObjectFlow
- SpecIF:Visibility: Public

## uml:ObjectFlow R-093c4d80-5158-4afc-8c81-f2fe13a20051 (FMC:State)
- dcterms:title: NoName
- dcterms:type: uml:ObjectFlow
- SpecIF:Visibility: Public

## uml:ObjectFlow R-c06add13-d722-4aaf-b34e-cacbf5b3ce18 (FMC:State)
- dcterms:title: NoName
- dcterms:type: uml:ObjectFlow
- SpecIF:Visibility: Public

## uml:ObjectFlow R-c7ce3c0e-b316-47be-aa82-dc9e0451204b (FMC:State)
- dcterms:title: NoName
- dcterms:type: uml:ObjectFlow
- SpecIF:Visibility: Public

## uml:ObjectFlow R-e60370a4-14bb-4b84-ad88-b82ce813930c (FMC:State)
- dcterms:title: NoName
- dcterms:type: uml:ObjectFlow
- SpecIF:Visibility: Public

## Yes R-c787d73e-2223-4d08-961d-e1692959063d (FMC:State)
- dcterms:title: Yes
- dcterms:type: uml:ObjectFlow
- SpecIF:Visibility: Public

## No R-d40e1e83-e46a-4ac6-9044-24045398829d (FMC:State)
- dcterms:title: No
- dcterms:type: uml:ObjectFlow
- SpecIF:Visibility: Public

## uml:ObjectFlow R-b8f69021-433c-47ff-afc3-24170b4dfff5 (FMC:State)
- dcterms:title: NoName
- dcterms:type: uml:ObjectFlow
- SpecIF:Visibility: Public

## uml:ObjectFlow R-1978714c-8fb0-4b7f-a5e8-75dea25bd7a4 (FMC:State)
- dcterms:title: NoName
- dcterms:type: uml:ObjectFlow
- SpecIF:Visibility: Public

## uml:ObjectFlow R-2b9eb992-2d2f-4766-a47f-f796be9032a6 (FMC:State)
- dcterms:title: NoName
- dcterms:type: uml:ObjectFlow
- SpecIF:Visibility: Public

## uml:ObjectFlow R-dcc15ebb-328e-44d9-a1e9-03e149787af7 (FMC:State)
- dcterms:title: NoName
- dcterms:type: uml:ObjectFlow
- SpecIF:Visibility: Public

## Yes R-43458eec-b4d3-4cf7-9553-248c3ae8300d (FMC:State)
- dcterms:title: Yes
- dcterms:type: uml:ObjectFlow
- SpecIF:Visibility: Public

## No R-e89156c3-0b3c-43b9-bb62-443f89bdc9a3 (FMC:State)
- dcterms:title: No
- dcterms:type: uml:ObjectFlow
- SpecIF:Visibility: Public

## uml:ObjectFlow R-fd015af1-ace8-4115-8c0c-96e9857bff5b (FMC:State)
- dcterms:title: NoName
- dcterms:type: uml:ObjectFlow
- SpecIF:Visibility: Public

## uml:ObjectFlow R-e38c3857-79bf-4951-9982-d31955c69aff (FMC:State)
- dcterms:title: NoName
- dcterms:type: uml:ObjectFlow
- SpecIF:Visibility: Public

## uml:ObjectFlow R-0a539b48-fa22-4dd7-996e-348becb0eaf7 (FMC:State)
- dcterms:title: NoName
- dcterms:type: uml:ObjectFlow
- SpecIF:Visibility: Public

## uml:ObjectFlow R-9cce8d51-b325-4d94-8fb5-af07a85ad290 (FMC:State)
- dcterms:title: NoName
- dcterms:type: uml:ObjectFlow
- SpecIF:Visibility: Public

## uml:ObjectFlow R-84a22798-7eb4-43f7-8a0b-bfc206d79a20 (FMC:State)
- dcterms:title: NoName
- dcterms:type: uml:ObjectFlow
- SpecIF:Visibility: Public

## uml:ObjectFlow R-1da5d190-4889-4241-b0fc-13860660630f (FMC:State)
- dcterms:title: NoName
- dcterms:type: uml:ObjectFlow
- SpecIF:Visibility: Public

## uml:ObjectFlow R-96f49cde-a389-4216-8cec-717e1de29045 (FMC:State)
- dcterms:title: NoName
- dcterms:type: uml:ObjectFlow
- SpecIF:Visibility: Public

## uml:ObjectFlow R-20a0dd2c-ab76-44bc-94cc-2c2d8d7f1220 (FMC:State)
- dcterms:title: NoName
- dcterms:type: uml:ObjectFlow
- SpecIF:Visibility: Public

## uml:ObjectFlow R-6e6b65ce-d5a1-4c13-97d7-6958414af21d (FMC:State)
- dcterms:title: NoName
- dcterms:type: uml:ObjectFlow
- SpecIF:Visibility: Public

## uml:OutputPin R-7be64e1e-7ef2-4eb8-8e5f-9b4fc8a5d788 (FMC:Actor)
- dcterms:title: NoName
- dcterms:type: uml:OutputPin
- SpecIF:Visibility: Public

## uml:InputPin R-256076da-614c-4c2f-9c42-f9434d933314 (FMC:Actor)
- dcterms:title: NoName
- dcterms:type: uml:InputPin
- SpecIF:Visibility: Public

## uml:OutputPin R-c9ef2015-1b11-4bc5-9bbc-f187331d720d (FMC:Actor)
- dcterms:title: NoName
- dcterms:type: uml:OutputPin
- SpecIF:Visibility: Public

## uml:InputPin R-a5ca7d1f-3bb9-4763-9471-d1b3e0b47320 (FMC:Actor)
- dcterms:title: NoName
- dcterms:type: uml:InputPin
- SpecIF:Visibility: Public

## uml:OutputPin R-f7dad4de-8410-4596-abb9-c7688ecab88c (FMC:Actor)
- dcterms:title: NoName
- dcterms:type: uml:OutputPin
- SpecIF:Visibility: Public

## uml:InputPin R-a03f6562-6341-4cf9-a989-582a5fe326be (FMC:Actor)
- dcterms:title: NoName
- dcterms:type: uml:InputPin
- SpecIF:Visibility: Public

## uml:OutputPin R-207f6369-061f-4582-90eb-2f131f445c6e (FMC:Actor)
- dcterms:title: NoName
- dcterms:type: uml:OutputPin
- SpecIF:Visibility: Public

## uml:InputPin R-10fcd591-929d-4d2d-90b4-415c61256529 (FMC:Actor)
- dcterms:title: NoName
- dcterms:type: uml:InputPin
- SpecIF:Visibility: Public

## uml:OutputPin R-786d85d7-bcf3-4765-8378-ba6f12d352e9 (FMC:Actor)
- dcterms:title: NoName
- dcterms:type: uml:OutputPin
- SpecIF:Visibility: Public

## uml:InputPin R-7b75e063-d629-42ae-b8d3-76eceb7ccb79 (FMC:Actor)
- dcterms:title: NoName
- dcterms:type: uml:InputPin
- SpecIF:Visibility: Public

## uml:OutputPin R-0f0d98f0-1923-4da8-aec3-e7b60b8cd5f0 (FMC:Actor)
- dcterms:title: NoName
- dcterms:type: uml:OutputPin
- SpecIF:Visibility: Public

## uml:InputPin R-243a6ebc-0ae9-4f64-8d4d-1c25e178b755 (FMC:Actor)
- dcterms:title: NoName
- dcterms:type: uml:InputPin
- SpecIF:Visibility: Public

## uml:OutputPin R-3bf67f53-b145-45ac-87aa-b1aeff5d99ad (FMC:Actor)
- dcterms:title: NoName
- dcterms:type: uml:OutputPin
- SpecIF:Visibility: Public

## uml:InputPin R-305a6bba-e8c9-42b7-82a1-e6b5a2407876 (FMC:Actor)
- dcterms:title: NoName
- dcterms:type: uml:InputPin
- SpecIF:Visibility: Public

## uml:OutputPin R-996a7ceb-e5e9-447b-83a1-3a6693d6edbd (FMC:Actor)
- dcterms:title: NoName
- dcterms:type: uml:OutputPin
- SpecIF:Visibility: Public

## uml:InputPin R-45148bd6-1eb8-4789-905b-f63de1488efc (FMC:Actor)
- dcterms:title: NoName
- dcterms:type: uml:InputPin
- SpecIF:Visibility: Public

## uml:InputPin R-dd8e7c3f-2bcd-4317-857a-71abfe127dda (FMC:Actor)
- dcterms:title: NoName
- dcterms:type: uml:InputPin
- SpecIF:Visibility: Public

## uml:OutputPin R-3b88cb31-5952-4545-921d-d2908c27b9c3 (FMC:Actor)
- dcterms:title: NoName
- dcterms:type: uml:OutputPin
- SpecIF:Visibility: Public

## uml:InputPin R-3541d240-105d-4818-949d-87c057aff000 (FMC:Actor)
- dcterms:title: NoName
- dcterms:type: uml:InputPin
- SpecIF:Visibility: Public

## uml:OutputPin R-37e6c947-1bc8-47bf-8a8b-2b619d049ac5 (FMC:Actor)
- dcterms:title: NoName
- dcterms:type: uml:OutputPin
- SpecIF:Visibility: Public

## uml:InputPin R-4fc2f7a8-7cb9-4567-a977-57b73a817b5e (FMC:Actor)
- dcterms:title: NoName
- dcterms:type: uml:InputPin
- SpecIF:Visibility: Public

## uml:OutputPin R-65e7e87c-416c-41b5-b6fb-4a07dc4d2105 (FMC:Actor)
- dcterms:title: NoName
- dcterms:type: uml:OutputPin
- SpecIF:Visibility: Public

## uml:InputPin R-0540b7f7-adaf-420e-b422-af5e67b71923 (FMC:Actor)
- dcterms:title: NoName
- dcterms:type: uml:InputPin
- SpecIF:Visibility: Public

## uml:OutputPin R-a9775afb-f759-4d9f-b467-7b55eef78a2e (FMC:Actor)
- dcterms:title: NoName
- dcterms:type: uml:OutputPin
- SpecIF:Visibility: Public

## uml:InputPin R-840f9e69-4d76-45c9-81c4-8d62d4b2bd6d (FMC:Actor)
- dcterms:title: NoName
- dcterms:type: uml:InputPin
- SpecIF:Visibility: Public

## uml:OutputPin R-a9f64978-3035-4f37-b6dc-c2dfde13f07e (FMC:Actor)
- dcterms:title: NoName
- dcterms:type: uml:OutputPin
- SpecIF:Visibility: Public

## uml:OutputPin R-319b5d61-0e4d-4686-8909-a1fec5c7b4be (FMC:Actor)
- dcterms:title: NoName
- dcterms:type: uml:OutputPin
- SpecIF:Visibility: Public

## shengen Passenger travelling into shengen-country? R-db720a37-410d-4b6e-ba54-335f20f1be54 (FMC:Actor)
- dcterms:title: shengen Passenger travelling into shengen-country?
- dcterms:type: uml:DecisionNode
- SpecIF:Visibility: Public

## shengen Passenger travelling into shengen-country? R-6345af52-6fdc-40a5-9c4f-0ede16b03fcd (FMC:Event)
- dcterms:title: shengen Passenger travelling into shengen-country?
- dcterms:type: uml:DecisionNode
- SpecIF:Visibility: Public

## shengen Passenger travelling into shengen-country? R-0cd79481-ef37-47d6-8351-481fde0fd5a7 (FMC:Event)
- dcterms:title: shengen Passenger travelling into shengen-country?
- dcterms:type: uml:DecisionNode
- SpecIF:Visibility: Public

## Ground Handling Service build up? R-7ab152e4-fd46-4ed3-ab1f-588ab84ccacb (FMC:Actor)
- dcterms:title: Ground Handling Service build up?
- dcterms:type: uml:DecisionNode
- SpecIF:Visibility: Public

## Ground Handling Service build up? R-643895db-88c8-4071-9ee3-21c60a0db3a6 (FMC:Event)
- dcterms:title: Ground Handling Service build up?
- dcterms:type: uml:DecisionNode
- SpecIF:Visibility: Public

## Ground Handling Service build up? R-2e55ce6b-8a28-4a14-b2eb-af9f49efdc18 (FMC:Event)
- dcterms:title: Ground Handling Service build up?
- dcterms:type: uml:DecisionNode
- SpecIF:Visibility: Public

## Statements
- CabinProcess SpecIF:precedes Join2
- Fork SpecIF:precedes CabinProcess
- Airline perform flight SpecIF:signals uml:ActivityFinalNode R-cff8cccc-c718-4566-987c-da9cc4afad7c
- uml:InitialNode R-93b07a3b-9716-418f-a49a-de4eaaec3587 SpecIF:triggers provide flight information
- uml:OutputPin R-7be64e1e-7ef2-4eb8-8e5f-9b4fc8a5d788 SpecIF:writes uml:ObjectFlow R-85178790-88ab-4da8-b3d7-e836021892c5
- uml:InputPin R-256076da-614c-4c2f-9c42-f9434d933314 SpecIF:reads uml:ObjectFlow R-85178790-88ab-4da8-b3d7-e836021892c5
- provide flight information SpecIF:precedes hand over baggage
- uml:OutputPin R-c9ef2015-1b11-4bc5-9bbc-f187331d720d SpecIF:writes uml:ObjectFlow R-66d6ec78-4152-434a-984d-ed5abe8756a1
- Fork SpecIF:reads uml:ObjectFlow R-66d6ec78-4152-434a-984d-ed5abe8756a1
- hand over baggage SpecIF:precedes Fork
- Fork SpecIF:writes uml:ObjectFlow R-1f22f535-4c9d-4cee-b743-573de1111ccc
- uml:InputPin R-a5ca7d1f-3bb9-4763-9471-d1b3e0b47320 SpecIF:reads uml:ObjectFlow R-1f22f535-4c9d-4cee-b743-573de1111ccc
- Fork SpecIF:precedes registration of Passenger
- Fork SpecIF:writes uml:ObjectFlow R-093c4d80-5158-4afc-8c81-f2fe13a20051
- uml:InputPin R-a03f6562-6341-4cf9-a989-582a5fe326be SpecIF:reads uml:ObjectFlow R-093c4d80-5158-4afc-8c81-f2fe13a20051
- Fork SpecIF:precedes check in baggage
- uml:OutputPin R-207f6369-061f-4582-90eb-2f131f445c6e SpecIF:writes uml:ObjectFlow R-c06add13-d722-4aaf-b34e-cacbf5b3ce18
- uml:InputPin R-7b75e063-d629-42ae-b8d3-76eceb7ccb79 SpecIF:reads uml:ObjectFlow R-c06add13-d722-4aaf-b34e-cacbf5b3ce18
- check in baggage SpecIF:precedes baggage security check
- uml:OutputPin R-f7dad4de-8410-4596-abb9-c7688ecab88c SpecIF:writes uml:ObjectFlow R-c7ce3c0e-b316-47be-aa82-dc9e0451204b
- uml:InputPin R-10fcd591-929d-4d2d-90b4-415c61256529 SpecIF:reads uml:ObjectFlow R-c7ce3c0e-b316-47be-aa82-dc9e0451204b
- registration of Passenger SpecIF:precedes security check
- uml:OutputPin R-3bf67f53-b145-45ac-87aa-b1aeff5d99ad SpecIF:writes uml:ObjectFlow R-b8f69021-433c-47ff-afc3-24170b4dfff5
- uml:MergeNode R-8da17d7f-141e-4b98-9a26-b949e61b0bc7 SpecIF:reads uml:ObjectFlow R-b8f69021-433c-47ff-afc3-24170b4dfff5
- border control SpecIF:precedes uml:MergeNode R-8da17d7f-141e-4b98-9a26-b949e61b0bc7
- Join2 SpecIF:writes uml:ObjectFlow R-1978714c-8fb0-4b7f-a5e8-75dea25bd7a4
- uml:InputPin R-45148bd6-1eb8-4789-905b-f63de1488efc SpecIF:reads uml:ObjectFlow R-1978714c-8fb0-4b7f-a5e8-75dea25bd7a4
- Join2 SpecIF:precedes Airline perform flight
- uml:OutputPin R-0f0d98f0-1923-4da8-aec3-e7b60b8cd5f0 SpecIF:writes uml:ObjectFlow R-2b9eb992-2d2f-4766-a47f-f796be9032a6
- uml:InputPin R-dd8e7c3f-2bcd-4317-857a-71abfe127dda SpecIF:reads uml:ObjectFlow R-2b9eb992-2d2f-4766-a47f-f796be9032a6
- baggage security check SpecIF:precedes Baggage Handling System
- uml:OutputPin R-37e6c947-1bc8-47bf-8a8b-2b619d049ac5 SpecIF:writes uml:ObjectFlow R-fd015af1-ace8-4115-8c0c-96e9857bff5b
- Merge SpecIF:reads uml:ObjectFlow R-fd015af1-ace8-4115-8c0c-96e9857bff5b
- Ground Handling Service build up bulk baggage cart SpecIF:precedes Merge
- uml:OutputPin R-65e7e87c-416c-41b5-b6fb-4a07dc4d2105 SpecIF:writes uml:ObjectFlow R-e38c3857-79bf-4951-9982-d31955c69aff
- Merge SpecIF:reads uml:ObjectFlow R-e38c3857-79bf-4951-9982-d31955c69aff
- build up Unit Load Devices SpecIF:precedes Merge
- uml:OutputPin R-a9f64978-3035-4f37-b6dc-c2dfde13f07e SpecIF:writes uml:ObjectFlow R-0a539b48-fa22-4dd7-996e-348becb0eaf7
- Join2 SpecIF:reads uml:ObjectFlow R-0a539b48-fa22-4dd7-996e-348becb0eaf7
- Ground Handling Service Load Baggage SpecIF:precedes Join2
- uml:OutputPin R-a9775afb-f759-4d9f-b467-7b55eef78a2e SpecIF:writes uml:ObjectFlow R-9cce8d51-b325-4d94-8fb5-af07a85ad290
- uml:InputPin R-840f9e69-4d76-45c9-81c4-8d62d4b2bd6d SpecIF:reads uml:ObjectFlow R-9cce8d51-b325-4d94-8fb5-af07a85ad290
- Transport Unit Load Devices to parking position SpecIF:precedes Ground Handling Service Load Baggage
- Merge SpecIF:writes uml:ObjectFlow R-84a22798-7eb4-43f7-8a0b-bfc206d79a20
- uml:InputPin R-0540b7f7-adaf-420e-b422-af5e67b71923 SpecIF:reads uml:ObjectFlow R-84a22798-7eb4-43f7-8a0b-bfc206d79a20
- Merge SpecIF:precedes Transport Unit Load Devices to parking position
- uml:OutputPin R-319b5d61-0e4d-4686-8909-a1fec5c7b4be SpecIF:writes uml:ObjectFlow R-1da5d190-4889-4241-b0fc-13860660630f
- Join1 SpecIF:reads uml:ObjectFlow R-1da5d190-4889-4241-b0fc-13860660630f
- Ready for Boarding SpecIF:precedes Join1
- uml:MergeNode R-8da17d7f-141e-4b98-9a26-b949e61b0bc7 SpecIF:writes uml:ObjectFlow R-96f49cde-a389-4216-8cec-717e1de29045
- Join1 SpecIF:reads uml:ObjectFlow R-96f49cde-a389-4216-8cec-717e1de29045
- uml:MergeNode R-8da17d7f-141e-4b98-9a26-b949e61b0bc7 SpecIF:precedes Join1
- Join1 SpecIF:writes uml:ObjectFlow R-20a0dd2c-ab76-44bc-94cc-2c2d8d7f1220
- uml:InputPin R-305a6bba-e8c9-42b7-82a1-e6b5a2407876 SpecIF:reads uml:ObjectFlow R-20a0dd2c-ab76-44bc-94cc-2c2d8d7f1220
- Join1 SpecIF:precedes Board Passenger
- uml:OutputPin R-996a7ceb-e5e9-447b-83a1-3a6693d6edbd SpecIF:writes uml:ObjectFlow R-6e6b65ce-d5a1-4c13-97d7-6958414af21d
- Join2 SpecIF:reads uml:ObjectFlow R-6e6b65ce-d5a1-4c13-97d7-6958414af21d
- Board Passenger SpecIF:precedes Join2
- uml:OutputPin R-786d85d7-bcf3-4765-8378-ba6f12d352e9 SpecIF:writes uml:ObjectFlow R-e60370a4-14bb-4b84-ad88-b82ce813930c
- shengen Passenger travelling into shengen-country? R-db720a37-410d-4b6e-ba54-335f20f1be54 SpecIF:reads uml:ObjectFlow R-e60370a4-14bb-4b84-ad88-b82ce813930c
- security check SpecIF:precedes shengen Passenger travelling into shengen-country? R-db720a37-410d-4b6e-ba54-335f20f1be54
- shengen Passenger travelling into shengen-country? R-db720a37-410d-4b6e-ba54-335f20f1be54 SpecIF:writes Yes R-c787d73e-2223-4d08-961d-e1692959063d
- uml:MergeNode R-8da17d7f-141e-4b98-9a26-b949e61b0bc7 SpecIF:reads Yes R-c787d73e-2223-4d08-961d-e1692959063d
- shengen Passenger travelling into shengen-country? R-db720a37-410d-4b6e-ba54-335f20f1be54 SpecIF:signals shengen Passenger travelling into shengen-country? R-6345af52-6fdc-40a5-9c4f-0ede16b03fcd
- shengen Passenger travelling into shengen-country? R-6345af52-6fdc-40a5-9c4f-0ede16b03fcd SpecIF:triggers uml:MergeNode R-8da17d7f-141e-4b98-9a26-b949e61b0bc7
- shengen Passenger travelling into shengen-country? R-db720a37-410d-4b6e-ba54-335f20f1be54 SpecIF:writes No R-d40e1e83-e46a-4ac6-9044-24045398829d
- uml:InputPin R-243a6ebc-0ae9-4f64-8d4d-1c25e178b755 SpecIF:reads No R-d40e1e83-e46a-4ac6-9044-24045398829d
- shengen Passenger travelling into shengen-country? R-db720a37-410d-4b6e-ba54-335f20f1be54 SpecIF:signals shengen Passenger travelling into shengen-country? R-0cd79481-ef37-47d6-8351-481fde0fd5a7
- shengen Passenger travelling into shengen-country? R-0cd79481-ef37-47d6-8351-481fde0fd5a7 SpecIF:triggers border control
- uml:OutputPin R-3b88cb31-5952-4545-921d-d2908c27b9c3 SpecIF:writes uml:ObjectFlow R-dcc15ebb-328e-44d9-a1e9-03e149787af7
- Ground Handling Service build up? R-7ab152e4-fd46-4ed3-ab1f-588ab84ccacb SpecIF:reads uml:ObjectFlow R-dcc15ebb-328e-44d9-a1e9-03e149787af7
- Baggage Handling System SpecIF:precedes Ground Handling Service build up? R-7ab152e4-fd46-4ed3-ab1f-588ab84ccacb
- Ground Handling Service build up? R-7ab152e4-fd46-4ed3-ab1f-588ab84ccacb SpecIF:writes Yes R-43458eec-b4d3-4cf7-9553-248c3ae8300d
- uml:InputPin R-3541d240-105d-4818-949d-87c057aff000 SpecIF:reads Yes R-43458eec-b4d3-4cf7-9553-248c3ae8300d
- Ground Handling Service build up? R-7ab152e4-fd46-4ed3-ab1f-588ab84ccacb SpecIF:signals Ground Handling Service build up? R-643895db-88c8-4071-9ee3-21c60a0db3a6
- Ground Handling Service build up? R-643895db-88c8-4071-9ee3-21c60a0db3a6 SpecIF:triggers Ground Handling Service build up bulk baggage cart
- Ground Handling Service build up? R-7ab152e4-fd46-4ed3-ab1f-588ab84ccacb SpecIF:writes No R-e89156c3-0b3c-43b9-bb62-443f89bdc9a3
- uml:InputPin R-4fc2f7a8-7cb9-4567-a977-57b73a817b5e SpecIF:reads No R-e89156c3-0b3c-43b9-bb62-443f89bdc9a3
- Ground Handling Service build up? R-7ab152e4-fd46-4ed3-ab1f-588ab84ccacb SpecIF:signals Ground Handling Service build up? R-2e55ce6b-8a28-4a14-b2eb-af9f49efdc18
- Ground Handling Service build up? R-2e55ce6b-8a28-4a14-b2eb-af9f49efdc18 SpecIF:triggers build up Unit Load Devices
- ReadytoBoard_Signal SpecIF:triggers Ready for Boarding
- provide flight information SpecIF:contains uml:OutputPin R-7be64e1e-7ef2-4eb8-8e5f-9b4fc8a5d788
- hand over baggage SpecIF:contains uml:InputPin R-256076da-614c-4c2f-9c42-f9434d933314
- hand over baggage SpecIF:contains uml:OutputPin R-c9ef2015-1b11-4bc5-9bbc-f187331d720d
- registration of Passenger SpecIF:contains uml:InputPin R-a5ca7d1f-3bb9-4763-9471-d1b3e0b47320
- registration of Passenger SpecIF:contains uml:OutputPin R-f7dad4de-8410-4596-abb9-c7688ecab88c
- check in baggage SpecIF:contains uml:InputPin R-a03f6562-6341-4cf9-a989-582a5fe326be
- check in baggage SpecIF:contains uml:OutputPin R-207f6369-061f-4582-90eb-2f131f445c6e
- security check SpecIF:contains uml:InputPin R-10fcd591-929d-4d2d-90b4-415c61256529
- security check SpecIF:contains uml:OutputPin R-786d85d7-bcf3-4765-8378-ba6f12d352e9
- baggage security check SpecIF:contains uml:InputPin R-7b75e063-d629-42ae-b8d3-76eceb7ccb79
- baggage security check SpecIF:contains uml:OutputPin R-0f0d98f0-1923-4da8-aec3-e7b60b8cd5f0
- border control SpecIF:contains uml:InputPin R-243a6ebc-0ae9-4f64-8d4d-1c25e178b755
- border control SpecIF:contains uml:OutputPin R-3bf67f53-b145-45ac-87aa-b1aeff5d99ad
- Board Passenger SpecIF:contains uml:InputPin R-305a6bba-e8c9-42b7-82a1-e6b5a2407876
- Board Passenger SpecIF:contains uml:OutputPin R-996a7ceb-e5e9-447b-83a1-3a6693d6edbd
- Airline perform flight SpecIF:contains uml:InputPin R-45148bd6-1eb8-4789-905b-f63de1488efc
- Baggage Handling System SpecIF:contains uml:InputPin R-dd8e7c3f-2bcd-4317-857a-71abfe127dda
- Baggage Handling System SpecIF:contains uml:OutputPin R-3b88cb31-5952-4545-921d-d2908c27b9c3
- Ground Handling Service build up bulk baggage cart SpecIF:contains uml:InputPin R-3541d240-105d-4818-949d-87c057aff000
- Ground Handling Service build up bulk baggage cart SpecIF:contains uml:OutputPin R-37e6c947-1bc8-47bf-8a8b-2b619d049ac5
- build up Unit Load Devices SpecIF:contains uml:InputPin R-4fc2f7a8-7cb9-4567-a977-57b73a817b5e
- build up Unit Load Devices SpecIF:contains uml:OutputPin R-65e7e87c-416c-41b5-b6fb-4a07dc4d2105
- Transport Unit Load Devices to parking position SpecIF:contains uml:InputPin R-0540b7f7-adaf-420e-b422-af5e67b71923
- Transport Unit Load Devices to parking position SpecIF:contains uml:OutputPin R-a9775afb-f759-4d9f-b467-7b55eef78a2e
- Ground Handling Service Load Baggage SpecIF:contains uml:InputPin R-840f9e69-4d76-45c9-81c4-8d62d4b2bd6d
- Ground Handling Service Load Baggage SpecIF:contains uml:OutputPin R-a9f64978-3035-4f37-b6dc-c2dfde13f07e
- Ready for Boarding SpecIF:contains uml:OutputPin R-319b5d61-0e4d-4686-8909-a1fec5c7b4be
- Passenger Handling SpecIF:contains uml:ObjectFlow R-96f49cde-a389-4216-8cec-717e1de29045
- Passenger Handling SpecIF:contains Yes R-c787d73e-2223-4d08-961d-e1692959063d
- Passenger Handling SpecIF:contains No R-d40e1e83-e46a-4ac6-9044-24045398829d
- Passenger Handling SpecIF:contains uml:MergeNode R-8da17d7f-141e-4b98-9a26-b949e61b0bc7
- Passenger Handling SpecIF:contains registration of Passenger
- Passenger Handling SpecIF:contains security check
- Passenger Handling SpecIF:contains shengen Passenger travelling into shengen-country? R-db720a37-410d-4b6e-ba54-335f20f1be54
- Passenger Handling SpecIF:contains shengen Passenger travelling into shengen-country? R-6345af52-6fdc-40a5-9c4f-0ede16b03fcd
- Passenger Handling SpecIF:contains shengen Passenger travelling into shengen-country? R-0cd79481-ef37-47d6-8351-481fde0fd5a7
- Passenger Handling SpecIF:contains border control
- Passenger Handling SpecIF:contains Ready for Boarding
- Passenger Handling SpecIF:contains Board Passenger
- Bagage Handling SpecIF:contains No R-e89156c3-0b3c-43b9-bb62-443f89bdc9a3
- Bagage Handling SpecIF:contains Yes R-43458eec-b4d3-4cf7-9553-248c3ae8300d
- Bagage Handling SpecIF:contains uml:ObjectFlow R-84a22798-7eb4-43f7-8a0b-bfc206d79a20
- Bagage Handling SpecIF:contains build up Unit Load Devices
- Bagage Handling SpecIF:contains check in baggage
- Bagage Handling SpecIF:contains Baggage Handling System
- Bagage Handling SpecIF:contains Ground Handling Service Load Baggage
- Bagage Handling SpecIF:contains baggage security check
- Bagage Handling SpecIF:contains Transport Unit Load Devices to parking position
- Bagage Handling SpecIF:contains Ground Handling Service build up bulk baggage cart
- Bagage Handling SpecIF:contains Ground Handling Service build up? R-7ab152e4-fd46-4ed3-ab1f-588ab84ccacb
- Bagage Handling SpecIF:contains Ground Handling Service build up? R-643895db-88c8-4071-9ee3-21c60a0db3a6
- Bagage Handling SpecIF:contains Ground Handling Service build up? R-2e55ce6b-8a28-4a14-b2eb-af9f49efdc18
- Bagage Handling SpecIF:contains Merge
- AirportProcess SpecIF:shows Ground Handling Service build up bulk baggage cart
- AirportProcess SpecIF:shows uml:InputPin R-840f9e69-4d76-45c9-81c4-8d62d4b2bd6d
- AirportProcess SpecIF:shows uml:OutputPin R-0f0d98f0-1923-4da8-aec3-e7b60b8cd5f0
- AirportProcess SpecIF:shows Transport Unit Load Devices to parking position
- AirportProcess SpecIF:shows uml:ObjectFlow R-2b9eb992-2d2f-4766-a47f-f796be9032a6
- AirportProcess SpecIF:shows baggage security check
- AirportProcess SpecIF:shows uml:InputPin R-0540b7f7-adaf-420e-b422-af5e67b71923
- AirportProcess SpecIF:shows uml:OutputPin R-65e7e87c-416c-41b5-b6fb-4a07dc4d2105
- AirportProcess SpecIF:shows provide flight information
- AirportProcess SpecIF:shows uml:InputPin R-243a6ebc-0ae9-4f64-8d4d-1c25e178b755
- AirportProcess SpecIF:shows uml:InitialNode R-93b07a3b-9716-418f-a49a-de4eaaec3587
- AirportProcess SpecIF:shows uml:OutputPin R-3bf67f53-b145-45ac-87aa-b1aeff5d99ad
- AirportProcess SpecIF:shows Ground Handling Service build up? R-7ab152e4-fd46-4ed3-ab1f-588ab84ccacb
- AirportProcess SpecIF:shows Ground Handling Service build up? R-643895db-88c8-4071-9ee3-21c60a0db3a6
- AirportProcess SpecIF:shows Ground Handling Service build up? R-2e55ce6b-8a28-4a14-b2eb-af9f49efdc18
- AirportProcess SpecIF:shows security check
- AirportProcess SpecIF:shows uml:InputPin R-4fc2f7a8-7cb9-4567-a977-57b73a817b5e
- AirportProcess SpecIF:shows CabinProcess
- AirportProcess SpecIF:shows Yes R-43458eec-b4d3-4cf7-9553-248c3ae8300d
- AirportProcess SpecIF:shows Passenger Handling
- AirportProcess SpecIF:shows uml:ActivityFinalNode R-cff8cccc-c718-4566-987c-da9cc4afad7c
- AirportProcess SpecIF:shows uml:ObjectFlow R-093c4d80-5158-4afc-8c81-f2fe13a20051
- AirportProcess SpecIF:shows uml:ObjectFlow R-0a539b48-fa22-4dd7-996e-348becb0eaf7
- AirportProcess SpecIF:shows Join2
- AirportProcess SpecIF:shows border control
- AirportProcess SpecIF:shows Ready for Boarding
- AirportProcess SpecIF:shows uml:ObjectFlow R-84a22798-7eb4-43f7-8a0b-bfc206d79a20
- AirportProcess SpecIF:shows uml:InputPin R-dd8e7c3f-2bcd-4317-857a-71abfe127dda
- AirportProcess SpecIF:shows No R-d40e1e83-e46a-4ac6-9044-24045398829d
- AirportProcess SpecIF:shows uml:OutputPin R-786d85d7-bcf3-4765-8378-ba6f12d352e9
- AirportProcess SpecIF:shows Airline perform flight
- AirportProcess SpecIF:shows uml:ObjectFlow R-dcc15ebb-328e-44d9-a1e9-03e149787af7
- AirportProcess SpecIF:shows uml:InputPin R-a5ca7d1f-3bb9-4763-9471-d1b3e0b47320
- AirportProcess SpecIF:shows uml:MergeNode R-8da17d7f-141e-4b98-9a26-b949e61b0bc7
- AirportProcess SpecIF:shows Baggage Handling System
- AirportProcess SpecIF:shows uml:ObjectFlow R-c06add13-d722-4aaf-b34e-cacbf5b3ce18
- AirportProcess SpecIF:shows uml:ObjectFlow R-9cce8d51-b325-4d94-8fb5-af07a85ad290
- AirportProcess SpecIF:shows uml:ObjectFlow R-85178790-88ab-4da8-b3d7-e836021892c5
- AirportProcess SpecIF:shows uml:OutputPin R-c9ef2015-1b11-4bc5-9bbc-f187331d720d
- AirportProcess SpecIF:shows build up Unit Load Devices
- AirportProcess SpecIF:shows uml:InputPin R-a03f6562-6341-4cf9-a989-582a5fe326be
- AirportProcess SpecIF:shows hand over baggage
- AirportProcess SpecIF:shows uml:OutputPin R-996a7ceb-e5e9-447b-83a1-3a6693d6edbd
- AirportProcess SpecIF:shows uml:ObjectFlow R-fd015af1-ace8-4115-8c0c-96e9857bff5b
- AirportProcess SpecIF:shows uml:InputPin R-10fcd591-929d-4d2d-90b4-415c61256529
- AirportProcess SpecIF:shows uml:OutputPin R-319b5d61-0e4d-4686-8909-a1fec5c7b4be
- AirportProcess SpecIF:shows shengen Passenger travelling into shengen-country? R-db720a37-410d-4b6e-ba54-335f20f1be54
- AirportProcess SpecIF:shows shengen Passenger travelling into shengen-country? R-6345af52-6fdc-40a5-9c4f-0ede16b03fcd
- AirportProcess SpecIF:shows shengen Passenger travelling into shengen-country? R-0cd79481-ef37-47d6-8351-481fde0fd5a7
- AirportProcess SpecIF:shows check in baggage
- AirportProcess SpecIF:shows uml:ObjectFlow R-e38c3857-79bf-4951-9982-d31955c69aff
- AirportProcess SpecIF:shows Fork
- AirportProcess SpecIF:shows Merge
- AirportProcess SpecIF:shows uml:ObjectFlow R-96f49cde-a389-4216-8cec-717e1de29045
- AirportProcess SpecIF:shows uml:InputPin R-45148bd6-1eb8-4789-905b-f63de1488efc
- AirportProcess SpecIF:shows uml:ObjectFlow R-66d6ec78-4152-434a-984d-ed5abe8756a1
- AirportProcess SpecIF:shows No R-e89156c3-0b3c-43b9-bb62-443f89bdc9a3
- AirportProcess SpecIF:shows uml:ObjectFlow R-c7ce3c0e-b316-47be-aa82-dc9e0451204b
- AirportProcess SpecIF:shows uml:OutputPin R-7be64e1e-7ef2-4eb8-8e5f-9b4fc8a5d788
- AirportProcess SpecIF:shows uml:OutputPin R-3b88cb31-5952-4545-921d-d2908c27b9c3
- AirportProcess SpecIF:shows uml:OutputPin R-f7dad4de-8410-4596-abb9-c7688ecab88c
- AirportProcess SpecIF:shows uml:InputPin R-256076da-614c-4c2f-9c42-f9434d933314
- AirportProcess SpecIF:shows uml:ObjectFlow R-e60370a4-14bb-4b84-ad88-b82ce813930c
- AirportProcess SpecIF:shows uml:OutputPin R-a9775afb-f759-4d9f-b467-7b55eef78a2e
- AirportProcess SpecIF:shows uml:OutputPin R-a9f64978-3035-4f37-b6dc-c2dfde13f07e
- AirportProcess SpecIF:shows uml:InputPin R-7b75e063-d629-42ae-b8d3-76eceb7ccb79
- AirportProcess SpecIF:shows uml:ObjectFlow R-b8f69021-433c-47ff-afc3-24170b4dfff5
- AirportProcess SpecIF:shows uml:ObjectFlow R-1da5d190-4889-4241-b0fc-13860660630f
- AirportProcess SpecIF:shows registration of Passenger
- AirportProcess SpecIF:shows Ground Handling Service Load Baggage
- AirportProcess SpecIF:shows uml:ObjectFlow R-20a0dd2c-ab76-44bc-94cc-2c2d8d7f1220
- AirportProcess SpecIF:shows uml:OutputPin R-207f6369-061f-4582-90eb-2f131f445c6e
- AirportProcess SpecIF:shows uml:OutputPin R-37e6c947-1bc8-47bf-8a8b-2b619d049ac5
- AirportProcess SpecIF:shows uml:ObjectFlow R-6e6b65ce-d5a1-4c13-97d7-6958414af21d
- AirportProcess SpecIF:shows Bagage Handling
- AirportProcess SpecIF:shows Yes R-c787d73e-2223-4d08-961d-e1692959063d
- AirportProcess SpecIF:shows uml:ObjectFlow R-1978714c-8fb0-4b7f-a5e8-75dea25bd7a4
- AirportProcess SpecIF:shows Board Passenger
- AirportProcess SpecIF:shows Join1
- AirportProcess SpecIF:shows uml:InputPin R-3541d240-105d-4818-949d-87c057aff000
- AirportProcess SpecIF:shows uml:InputPin R-305a6bba-e8c9-42b7-82a1-e6b5a2407876
- AirportProcess SpecIF:shows uml:ObjectFlow R-1f22f535-4c9d-4cee-b743-573de1111ccc
