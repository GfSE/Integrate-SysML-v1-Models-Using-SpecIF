# Model_Template

## CabinProcess (FMC:Actor)
- dcterms:type: uml:Activity
- SpecIF:Visibility: Private

## CabinProcess (SpecIF:Diagram)
- dcterms:type: uml:Diagram
- SpecIF:Visibility: Public

## Model_CabinProcess (SpecIF:Collection)
- dcterms:description: Author:s-sruesch.
  Created:01.10.2012 15:10.
  Title:.
  Comment:.
- dcterms:type: uml:Model
- SpecIF:Visibility: Private

## Check Systems (FMC:Actor)
- dcterms:type: uml:CallBehaviorAction
- SpecIF:Visibility: Public

## Check Areas (FMC:Actor)
- dcterms:type: uml:CallBehaviorAction
- SpecIF:Visibility: Public

## Report (FMC:Actor)
- dcterms:type: uml:CallBehaviorAction
- SpecIF:Visibility: Public

## Preflight Briefing (FMC:Actor)
- dcterms:type: uml:CallBehaviorAction
- SpecIF:Visibility: Public

## Boarding of Crew (FMC:Actor)
- dcterms:type: uml:CallBehaviorAction
- SpecIF:Visibility: Public

## Positioning for boarding (FMC:Actor)
- dcterms:type: uml:CallBehaviorAction
- SpecIF:Visibility: Public

## Coordinate and Monitor Boarding (FMC:Actor)
- dcterms:type: uml:CallBehaviorAction
- SpecIF:Visibility: Public

## Check cabin after boarding (FMC:Actor)
- dcterms:type: uml:CallBehaviorAction
- SpecIF:Visibility: Public

## Close Boarding (FMC:Actor)
- dcterms:type: uml:CallBehaviorAction
- SpecIF:Visibility: Public

## NoName (FMC:Actor)
- dcterms:type: uml:ForkNode
- SpecIF:Visibility: Public

## Send Signal ReadytoBoard (FMC:Actor)
- dcterms:type: uml:SendSignalAction
- SpecIF:Visibility: Public

## NoName (FMC:Event)
- dcterms:type: uml:InitialNode
- SpecIF:Visibility: Public

## NoName (FMC:Event)
- dcterms:type: uml:ActivityFinalNode
- SpecIF:Visibility: Public

## ReadytoBoard_Signal (FMC:Event)
- dcterms:type: uml:Signal
- SpecIF:Visibility: Private

## Statements
- NoName SpecIF:triggers Preflight Briefing
- Preflight Briefing SpecIF:precedes Boarding of Crew
- Check Systems SpecIF:precedes Check Areas
- Check Areas SpecIF:precedes Report
- Report SpecIF:precedes Positioning for boarding
- Coordinate and Monitor Boarding SpecIF:precedes Check cabin after boarding
- Close Boarding SpecIF:signals NoName
- NoName SpecIF:precedes Send Signal ReadytoBoard
- Check cabin after boarding SpecIF:precedes Close Boarding
- NoName SpecIF:precedes Coordinate and Monitor Boarding
- Positioning for boarding SpecIF:precedes NoName
- Boarding of Crew SpecIF:precedes Check Systems
- Send Signal ReadytoBoard SpecIF:signals ReadytoBoard_Signal
- CabinProcess SpecIF:shows Boarding of Crew
- CabinProcess SpecIF:shows NoName
- CabinProcess SpecIF:shows Check cabin after boarding
- CabinProcess SpecIF:shows Check Systems
- CabinProcess SpecIF:shows Send Signal ReadytoBoard
- CabinProcess SpecIF:shows Report
- CabinProcess SpecIF:shows Close Boarding
- CabinProcess SpecIF:shows Coordinate and Monitor Boarding
- CabinProcess SpecIF:shows Preflight Briefing
- CabinProcess SpecIF:shows NoName
- CabinProcess SpecIF:shows NoName
- CabinProcess SpecIF:shows Check Areas
- CabinProcess SpecIF:shows Positioning for boarding
